(defun c:PIPEDIR ( / roadStart roadEnd roadAng pipes num i ent entData typ p1 p2 arrowStart left right tip len)
  (setq roadStart (getpoint "\nPick road start point: "))
  (setq roadEnd   (getpoint "\nPick road end point: "))
  (setq roadAng (angle roadStart roadEnd))
  (setq len 10.0)
  (setq pipes (ssget '((0 . "LINE,LWPOLYLINE"))))
  (if pipes
    (progn
      (setq num (sslength pipes) i 0)
      (repeat num
        (setq ent (ssname pipes i))
        (setq entData (entget ent))
        (setq typ (cdr (assoc 0 entData)))
        (cond
          ((= typ "LINE")
            (setq p1 (cdr (assoc 10 entData)))
            (setq p2 (cdr (assoc 11 entData)))
          )
          ((= typ "LWPOLYLINE")
            (setq p1 (cdr (assoc 10 entData)))
            (setq p2 (cdr (assoc 10 (reverse entData))))
          )
        )
        (setq arrowStart
          (if (< (distance p1 roadStart) (distance p2 roadStart)) p1 p2))
        (setq left (polar arrowStart (+ roadAng (/ pi 2)) (/ len 2)))
        (setq right (polar arrowStart (- roadAng (/ pi 2)) (/ len 2)))
        (setq tip (polar arrowStart roadAng len))
        (command "_.PLINE" left right tip "C")
        (setq i (1+ i))
      )
    )
  )
  (princ)
)
(princ "PIPEDIR loaded. Type PIPEDIR to run.\n")
